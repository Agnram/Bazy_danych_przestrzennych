FME workspace z3.fmw

Parameters:
- SourceDataset_SHAPEFILE = $(FME_MF_DIR)dane\bdline_essh_gb\Data\GB\scotland_and_wales_region.shp   # Source Esri Shapefile(s)
- SourceDataset_GEOTIFF_4 = ""D:\Studiowe_rzeczy\bazy_przestrzenne\Dane_cw8\ras250_gb\data\HP.tif" "D:\Studiowe_rzeczy\bazy_przestrzenne\Dane_cw8\ras250_gb\data\HT.tif" "D:\Studiowe_rzeczy\bazy_przestrzenne\Dane_cw8\ras250_gb\data\HU.tif" "D:\Studiowe_rzeczy\bazy_przestrzenne\Dane_cw8\ras250_gb\data\HW.tif" "D:\Studiowe_rzeczy\bazy_przestrzenne\Dane_cw8\ras250_gb\data\HX.tif" "D:\Studiowe_rzeczy\bazy_przestrzenne\Dane_cw8\ras250_gb\data\HY.tif" "D:\Studiowe_rzeczy\bazy_przestrzenne\Dane_cw8\ras250_gb\data\HZ.tif" "D:\Studiowe_rzeczy\bazy_przestrzenne\Dane_cw8\ras250_gb\data\NA.tif" "D:\Studiowe_rzeczy\bazy_przestrzenne\Dane_cw8\ras250_gb\data\NB.tif" "D:\Studiowe_rzeczy\bazy_przestrzenne\Dane_cw8\ras250_gb\data\NC.tif" "D:\Studiowe_rzeczy\bazy_przestrzenne\Dane_cw8\ras250_gb\data\ND.tif" "D:\Studiowe_rzeczy\bazy_przestrzenne\Dane_cw8\ras250_gb\data\NF.tif" "D:\Studiowe_rzeczy\bazy_przestrzenne\Dane_cw8\ras250_gb\data\NG.tif" "D:\Studiowe_rzeczy\bazy_przestrzenne\Dane_cw8\ras250_gb\data\NH.tif" "D:\Studiowe_rzeczy\bazy_przestrzenne\Dane_cw8\ras250_gb\data\NJ.tif" "D:\Studiowe_rzeczy\bazy_przestrzenne\Dane_cw8\ras250_gb\data\NK.tif" "D:\Studiowe_rzeczy\bazy_przestrzenne\Dane_cw8\ras250_gb\data\NL.tif" "D:\Studiowe_rzeczy\bazy_przestrzenne\Dane_cw8\ras250_gb\data\NM.tif" "D:\Studiowe_rzeczy\bazy_przestrzenne\Dane_cw8\ras250_gb\data\NN.tif" "D:\Studiowe_rzeczy\bazy_przestrzenne\Dane_cw8\ras250_gb\data\NO.tif" "D:\Studiowe_rzeczy\bazy_przestrzenne\Dane_cw8\ras250_gb\data\NR.tif" "D:\Studiowe_rzeczy\bazy_przestrzenne\Dane_cw8\ras250_gb\data\NS.tif" "D:\Studiowe_rzeczy\bazy_przestrzenne\Dane_cw8\ras250_gb\data\NT.tif" "D:\Studiowe_rzeczy\bazy_przestrzenne\Dane_cw8\ras250_gb\data\NU.tif" "D:\Studiowe_rzeczy\bazy_przestrzenne\Dane_cw8\ras250_gb\data\NW.tif" "D:\Studiowe_rzeczy\bazy_przestrzenne\Dane_cw8\ras250_gb\data\NX.tif" "D:\Studiowe_rzeczy\bazy_przestrzenne\Dane_cw8\ras250_gb\data\NY.tif" "D:\Studiowe_rzeczy\bazy_przestrzenne\Dane_cw8\ras250_gb\data\NZ.tif" "D:\Studiowe_rzeczy\bazy_przestrzenne\Dane_cw8\ras250_gb\data\OV.tif" "D:\Studiowe_rzeczy\bazy_przestrzenne\Dane_cw8\ras250_gb\data\SC.tif" "D:\Studiowe_rzeczy\bazy_przestrzenne\Dane_cw8\ras250_gb\data\SD.tif" "D:\Studiowe_rzeczy\bazy_przestrzenne\Dane_cw8\ras250_gb\data\SE.tif" "D:\Studiowe_rzeczy\bazy_przestrzenne\Dane_cw8\ras250_gb\data\SH.tif" "D:\Studiowe_rzeczy\bazy_przestrzenne\Dane_cw8\ras250_gb\data\SJ.tif" "D:\Studiowe_rzeczy\bazy_przestrzenne\Dane_cw8\ras250_gb\data\SK.tif" "D:\Studiowe_rzeczy\bazy_przestrzenne\Dane_cw8\ras250_gb\data\SM.tif" "D:\Studiowe_rzeczy\bazy_przestrzenne\Dane_cw8\ras250_gb\data\SN.tif" "D:\Studiowe_rzeczy\bazy_przestrzenne\Dane_cw8\ras250_gb\data\SO.tif" "D:\Studiowe_rzeczy\bazy_przestrzenne\Dane_cw8\ras250_gb\data\SP.tif" "D:\Studiowe_rzeczy\bazy_przestrzenne\Dane_cw8\ras250_gb\data\SR.tif" "D:\Studiowe_rzeczy\bazy_przestrzenne\Dane_cw8\ras250_gb\data\SS.tif" "D:\Studiowe_rzeczy\bazy_przestrzenne\Dane_cw8\ras250_gb\data\ST.tif" "D:\Studiowe_rzeczy\bazy_przestrzenne\Dane_cw8\ras250_gb\data\SU.tif" "D:\Studiowe_rzeczy\bazy_przestrzenne\Dane_cw8\ras250_gb\data\SV.tif" "D:\Studiowe_rzeczy\bazy_przestrzenne\Dane_cw8\ras250_gb\data\SW.tif" "D:\Studiowe_rzeczy\bazy_przestrzenne\Dane_cw8\ras250_gb\data\SX.tif" "D:\Studiowe_rzeczy\bazy_przestrzenne\Dane_cw8\ras250_gb\data\SY.tif" "D:\Studiowe_rzeczy\bazy_przestrzenne\Dane_cw8\ras250_gb\data\SZ.tif" "D:\Studiowe_rzeczy\bazy_przestrzenne\Dane_cw8\ras250_gb\data\TA.tif" "D:\Studiowe_rzeczy\bazy_przestrzenne\Dane_cw8\ras250_gb\data\TF.tif" "D:\Studiowe_rzeczy\bazy_przestrzenne\Dane_cw8\ras250_gb\data\TG.tif" "D:\Studiowe_rzeczy\bazy_przestrzenne\Dane_cw8\ras250_gb\data\TL.tif" "D:\Studiowe_rzeczy\bazy_przestrzenne\Dane_cw8\ras250_gb\data\TM.tif" "D:\Studiowe_rzeczy\bazy_przestrzenne\Dane_cw8\ras250_gb\data\TQ.tif" "D:\Studiowe_rzeczy\bazy_przestrzenne\Dane_cw8\ras250_gb\data\TR.tif" "D:\Studiowe_rzeczy\bazy_przestrzenne\Dane_cw8\ras250_gb\data\TV.tif""   # Source GeoTIFF File(s) or URL(s)
- DestDataset_POSTGIS = cw9z3   # Connection

Readers:
- SHAPEFILE_1: SHAPEFILE from $(SourceDataset_SHAPEFILE)
- GEOTIFF_1: GEOTIFF from $(SourceDataset_GEOTIFF_4)

Writers:
- POSTGIS_1: POSTGIS to $(DestDataset_POSTGIS)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = TEST
    PASSED -> Aggregator
Aggregator
    ACCUM_ATTRS_NAME = Use Attributes From One Feature
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> Exports (writer POSTGIS_1)
Exports (writer POSTGIS_1)
